module auto_config_agent {

    yang-version "1";

    // namespace
    namespace "urn:srl_test/auto-config-agent";

    prefix "auto_config_agent";

    // import srl_nokia-common {
    //    prefix srl_nokia-comm;
    // }

    // Note that this module needs to be in the path for source-directories
    import srl_nokia-extensions {
      prefix srl_nokia-ext;
    }

    revision "2021-04-11" {
        description "Initial revision";
        reference "TBD";
    }

    grouping auto-config-agent-top {
        description "Top level grouping for auto config agent sample app";

        container auto-config-agent {
            presence "presence container";
            description "Top level enclosing container for auto config agent sample app
                         config and operational state data";

            leaf role {
                description "Role of this node in the fabric (layer in the network)";
                type enumeration {
                 enum auto;      // Auto-determined: Start as spine, become leaf
                 enum leaf;
                 enum spine;
                 enum endpoint;  // Use SRL to emulate a Linux host
                 // TODO enum superspine;
                 // enum leaf-with-evpn; // Leaf with BGP EVPN/VXLAN overlay enabled?
                }
                default "auto";
            }
            leaf base-as {
                description "Baseline 2-byte or 4-byte Autonomous System to auto-assign";
                // type srl_nokia-comm:as-number;
                type uint32;
                // default 65000; // Use 2-byte AS for easier RT interop
                // see https://www.ipspace.net/Data_Center_BGP/EVPN_Route_Target_Considerations
                default 4200000000; // Spines get this, each leaf gets base+rank
            }
            leaf leaf-as {
                description "AS to use for leaves, 0=auto (eBGP)";
                // type srl_nokia-comm:as-number;
                type uint32;
                default 0; // Default base+rank = eBGP
            }
            leaf host-as {
                description "AS to use for hosts, 0=same as leaf (iBGP)";
                // type srl_nokia-comm:as-number;
                type uint32;
                default 0;
            }

            leaf peerlinks-prefix {
                description "IPv4 prefix range to use for auto-assigned peering links /31";
                // type srl_nokia-comm:ipv4-prefix;
                type string;
                default "192.168.127.0/24"; // enough for 128 /31 links
            }
            leaf loopbacks-prefix {
                description "IPv4 prefix range to use for auto-assigned loopback IPs /32";
                // type srl_nokia-comm:ipv4-prefix;
                type string;
                default "1.1.0.0/22"; // spines get 1.1.0.x, leaves 1.1.1.x
            }
            leaf max-spines {
                description "Maximum number of spines, controls IP link addressing; must match across fabric";
                type uint8;
                default 4; // Higher values require a larger peerlinks-prefix space
            }
            leaf max-leaves {
                description "Maximum number of leafs, controls AS allocation; must match across fabric";
                type uint16;
                default 16; // Currently only affects max AS that spines accept BGP peering from
            }
            leaf max-hosts-per-leaf {
                description "Maximum number of host ports per leaf, controls IP allocation; must match across fabric";
                type uint16;
                default 4; // Too high -> out of peer link IP space
            }
            leaf max-lag-links {
                description "Maximum number of links in a LAG bundle, controls IP allocation; must match across fabric";
                type uint8;
                default 4; // Too high -> out of peer link IP space
            }
            leaf use-evpn {
                description "Provision BGP EVPN control plane and VXLAN endpoints";
                type boolean;
                default false;
            }
            leaf use-ospfv3 {
                description "Provision OSPFv3 on fabric interfaces";
                type boolean;
                default false;
            }
            leaf auto-lags {
                description "Discover and provision LAGs on leaves, using LLDP";
                type boolean;
                default true;
            }

            // info from state
            list leaf {
                key leaf-id;
                config false;

                leaf leaf-id {
                  type string;
                }
                container lldp {
                 srl_nokia-ext:delivery-node-override true;
                 presence "State LLDP operational parameters";

                 list port {
                  key port-name;
                  leaf port-name {
                    type string;
                  }
                  container neighbor {
                   srl_nokia-ext:delivery-node-override true;
                   presence "State LLDP neighbor operational parameters";
                   leaf host-name {
                    type string;
                   }
                  }
                 }
                }
            }
        }
    }

    // data definition statements
    uses auto-config-agent-top;
}
